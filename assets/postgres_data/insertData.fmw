FME workspace insertData.fmw

Parameters:
- DestDataset_POSTGIS =
- DestDataset_POSTGIS_5 =
- SourceDataset_OGCGEOPACKAGE =
- SourceDataset_POSTGIS =

Readers:
- OGCGEOPACKAGE_1: OGCGEOPACKAGE from $(SourceDataset_OGCGEOPACKAGE) in EPSG:4326
- POSTGIS_1: POSTGIS from $(SourceDataset_POSTGIS)

Writers:
- POSTGIS_2: POSTGIS to $(DestDataset_POSTGIS)
- POSTGIS_4: POSTGIS to $(DestDataset_POSTGIS_5)

germany_bundeslaender (reader POSTGIS_1)
    attributes: name_1 text, uid float8, gid_0 text, name_0 text, gid_1 text, varname_1 text, nl_name_1 text, iso_1 text, hasc_1 text, cc_1 text, type_1 text, engtype_1 text, validfr_1 text
    -> public.germany_bundeslaender
public.germany_bundeslaender: Inspector
gadm404 (reader OGCGEOPACKAGE_1)
    attributes: UID double, GID_0 text(32), NAME_0 text(32), VARNAME_0 text(32), GID_1 text(32), NAME_1 text(32), VARNAME_1 text(32), NL_NAME_1 text(32), ISO_1 text(32), HASC_1 text(32), CC_1 text(32), TYPE_1 text(32), ENGTYPE_1 text(32), VALIDFR_1 text(32), GID_2 text(32), NAME_2 text(32), VARNAME_2 text(32), NL_NAME_2 text(32), HASC_2 text(32), CC_2 text(32), TYPE_2 text(32), ENGTYPE_2 text(32), VALIDFR_2 text(32), GID_3 text(32), NAME_3 text(32), VARNAME_3 text(32), NL_NAME_3 text(32), HASC_3 text(32), CC_3 text(32), TYPE_3 text(32),
      ENGTYPE_3 text(32), VALIDFR_3 text(32), GID_4 text(32), NAME_4 text(32), VARNAME_4 text(32), CC_4 text(32), TYPE_4 text(32), ENGTYPE_4 text(32), VALIDFR_4 text(32), GID_5 text(32), NAME_5 text(32), CC_5 text(32), TYPE_5 text(32), ENGTYPE_5 text(32), GOVERNEDBY text(32), SOVEREIGN text(32), DISPUTEDBY text(32), REGION text(32), VARREGION text(32), fid int,PrimaryKey
    -> Dissolver
    -> Tester_2
Tester_2
    BOOL_OP = OR
    COMPOSITE_TEST = 1
    TEST_CLAUSE = TEST @Value(NAME_0) = Germany
    TEST_MODE = TEST
    PASSED -> Dissolver_2
Dissolver_2
    ACCUM_INPUT_ATTRS = Use Attributes From One Feature
    CLEANING_TOLERANCE = Automatic
    CONNECT_Z_MODE = First Wins
    DEAGGREGATE_INPUT = Yes
    GROUP_BY = NAME_1
    AREA -> Aggregator_2
Aggregator_2
    ACCUM_ATTRS_NAME = Use Attributes From One Feature
    AGGREGATE_TYPE = Homogeneous Collection (If Possible)
    GROUP_BY = NAME_1
    MODE = Geometry - Assemble One Level
    SEP = ,
    AGGREGATE -> AttributeKeeper_2
AttributeKeeper_2
    CREATE_BULK_MODE_FEATURES = NO
    KEEP_ATTRS = GID_0,NAME_0,UID,CC_1,ENGTYPE_1,GID_1,HASC_1,ISO_1,NAME_1,NL_NAME_1,TYPE_1,VALIDFR_1,VARNAME_1,SOVEREIGN
    -> Generalizer
Generalizer
    ALG_TEXT = Douglas (Generalize)
    PRESERVE = No
    PRESERVE_PATHS = No
    TOLERANCE = 0.001
    -> CenterPointExtractor_2
CenterPointExtractor_2
    CENTX = lng_center
    CENTY = lat_center
    CENTZ = _inside_z
    EXTRACTIONMODE = CENTEROFGRAV
    -> AttributeRemover
AttributeRemover
    REMOVE_ATTRS = _inside_z
    -> germany_bundeslaender (writer POSTGIS_4)
germany_bundeslaender (writer POSTGIS_4)
    attributes: name_1 text, uid float8, gid_0 text, name_0 text, gid_1 text, varname_1 text, nl_name_1 text, iso_1 text, hasc_1 text, cc_1 text, type_1 text, engtype_1 text, validfr_1 text, sovereign text, lng_center float8, lat_center float8
Dissolver
    ACCUM_INPUT_ATTRS = Use Attributes From One Feature
    CLEANING_TOLERANCE = Automatic
    CONNECT_Z_MODE = First Wins
    DEAGGREGATE_INPUT = Yes
    GROUP_BY = NAME_0
    AREA -> Aggregator
Aggregator
    ACCUM_ATTRS_NAME = Use Attributes From One Feature
    AGGREGATE_TYPE = Homogeneous Collection (If Possible)
    GROUP_BY = NAME_0
    MODE = Geometry - Assemble One Level
    SEP = ,
    AGGREGATE -> Tester
Tester
    BOOL_OP = OR
    COMPOSITE_TEST = 1
    TEST_CLAUSE = TEST @Value(NAME_0) = Antarctica
    TEST_MODE = TEST
    FAILED -> AttributeKeeper_3
AttributeKeeper_3
    CREATE_BULK_MODE_FEATURES = NO
    KEEP_ATTRS = GID_0,NAME_0,UID,CC_1,ENGTYPE_1,GID_1,HASC_1,ISO_1,NAME_1,NL_NAME_1,TYPE_1,VALIDFR_1,VARNAME_1,SOVEREIGN
    -> Generalizer_2
Generalizer_2
    ALG_TEXT = Douglas (Generalize)
    PRESERVE = No
    PRESERVE_PATHS = No
    TOLERANCE = 0.001
    -> CenterPointExtractor
CenterPointExtractor
    CENTX = lng_center
    CENTY = lat_center
    CENTZ = _inside_z
    EXTRACTIONMODE = CENTEROFGRAV
    -> AttributeRemover_2
AttributeRemover_2
    REMOVE_ATTRS = _inside_z
    -> AttributeManager
AttributeManager
    ATTR_TABLE = RENAME_SET_VALUE ENGTYPE_1 > name_1_eng
    -> world_borders (writer POSTGIS_2)
world_borders (writer POSTGIS_2)
    attributes: name_0 text, uid float8, gid_0 text, gid_1 text, name_1 text, varname_1 text, nl_name_1 text, iso_1 text, hasc_1 text, cc_1 text, type_1 text, name_1_eng text, validfr_1 text, sovereign text, lng_center float8, lat_center float8
world_borders (reader POSTGIS_1)
    attributes: name_0 text, uid float8, gid_0 text, sovereign text, lng_center float8, lat_center float8
    -> public.world_borders
public.world_borders: Inspector
