FME workspace createDatasets.fmw

Parameters:
- DestDataset_JSON =
- DestDataset_JSON_10 =
- DestDataset_JSON_11 =
- DestDataset_JSON_12 =
- DestDataset_JSON_13 =
- DestDataset_JSON_14 =
- DestDataset_JSON_15 =
- DestDataset_JSON_9 =
- SourceDataset_CSV2 =
- SourceDataset_CSV2_3 =

Readers:
- CSV2_1: CSV2 from $(SourceDataset_CSV2)
- CSV2_2: CSV2 from $(SourceDataset_CSV2_3)

Writers:
- JSON_1: JSON to $(DestDataset_JSON)
- JSON_2: JSON to $(DestDataset_JSON_9)
- JSON_3: JSON to $(DestDataset_JSON_13)
- JSON_4: JSON to $(DestDataset_JSON_11)
- JSON_5: JSON to $(DestDataset_JSON_15)
- JSON_6: JSON to $(DestDataset_JSON_10)
- JSON_7: JSON to $(DestDataset_JSON_12)
- JSON_8: JSON to $(DestDataset_JSON_14)

Note: CSV: list_countries_with_iso_regions_continent [CSV2]
CSV (reader CSV2_2)
    attributes: No uint32, Country varchar(53), ISO3 varchar(4), M49Code uint32, Region1 varchar(26), Region2 varchar(32), Continent varchar(14)
    -> Tester_3
Tester_3
    BOOL_OP = OR
    COMPOSITE_TEST = 1
    TEST_CLAUSE = TEST ISO3 ATTRIBUTE_HAS_A_VALUE ""
    TEST_MODE = TEST
    PASSED -> FeatureJoiner [RIGHT]
Note: List of all cities
CSV (reader CSV2_1)
    attributes: city varchar(50), city_ascii varchar(50), lat real32, lng real64, country varchar(46), iso2 varchar(3), iso3 varchar(4), admin_name varchar(56), capital varchar(8), population real64, id uint32
    -> Tester
    -> CSV (writer JSON_1)
    -> Tester_2
    -> FeatureJoiner [LEFT]
Note: Alle cities
CSV (writer JSON_1)
    attributes: city string, city_ascii string, lat float, lng float, country string, iso2 string, iso3 string, admin_name string, capital string, population float, id int
Note: Capitals
Tester
    BOOL_OP = OR
    COMPOSITE_TEST = 1
    TEST_CLAUSE = TEST @Value(capital) = primary
    TEST_MODE = TEST
    PASSED -> CSV (writer JSON_3)
CSV (writer JSON_3)
    attributes: city string, city_ascii string, lat float, lng float, country string, iso2 string, iso3 string, admin_name string, capital string, population float, id int
Note: larger 250000
Tester_2
    BOOL_OP = OR
    COMPOSITE_TEST = 1
    TEST_CLAUSE = TEST @Value(population) > 250000
    TEST_MODE = TEST
    PASSED -> CSV (writer JSON_2)
CSV (writer JSON_2)
    attributes: city string, city_ascii string, lat float, lng float, country string, iso2 string, iso3 string, admin_name string, capital string, population float, id int
FeatureJoiner
    ATTR_CONFLICT_RES = Use Left
    GEOMETRY_HANDLING = Use Left
    JOIN_KEYS = iso3 ISO3 AUTO
    JOIN_MODE = Inner
    JOINED -> Tester_4
    JOINED -> Tester_6
    JOINED -> Tester_8
    JOINED -> Tester_10
Note: germany
Tester_4
    BOOL_OP = OR
    COMPOSITE_TEST = 1
    TEST_CLAUSE = TEST @Value(country) = Germany
    TEST_MODE = TEST
    PASSED -> CSV (writer JSON_4)
    PASSED -> Tester_5
CSV (writer JSON_4)
    attributes: city string, city_ascii string, lat float, lng float, country string, iso2 string, iso3 string, admin_name string, capital string, population float, id int
Note: larger 25000
Tester_5
    BOOL_OP = OR
    COMPOSITE_TEST = 1
    TEST_CLAUSE = TEST @Value(population) > 25000
    TEST_MODE = TEST
    PASSED -> CSV (writer JSON_5)
CSV (writer JSON_5)
    attributes: city string, city_ascii string, lat float, lng float, country string, iso2 string, iso3 string, admin_name string, capital string, population float, id int
Note: Japan
Tester_10
    BOOL_OP = OR
    COMPOSITE_TEST = 1
    TEST_CLAUSE = TEST @Value(country) = Japan
    TEST_MODE = TEST
    PASSED -> Tester_11
Note: larger 25000
Tester_11
    BOOL_OP = OR
    COMPOSITE_TEST = 1
    TEST_CLAUSE = TEST @Value(population) > 25000
    TEST_MODE = TEST
    PASSED -> CSV (writer JSON_8)
CSV (writer JSON_8)
    attributes: city string, city_ascii string, lat float, lng float, country string, iso2 string, iso3 string, admin_name string, capital string, population float, id int
Note: european
Tester_6
    BOOL_OP = OR
    COMPOSITE_TEST = 1
    TEST_CLAUSE = TEST @Value(Continent) = Europe
    TEST_MODE = TEST
    PASSED -> Tester_7
Note: larger 100000
Tester_7
    BOOL_OP = OR
    COMPOSITE_TEST = 1
    TEST_CLAUSE = TEST @Value(population) > 25000
    TEST_MODE = TEST
    PASSED -> CSV (writer JSON_6)
CSV (writer JSON_6)
    attributes: city string, city_ascii string, lat float, lng float, country string, iso2 string, iso3 string, admin_name string, capital string, population float, id int
Note: North America
Tester_8
    BOOL_OP = OR
    COMPOSITE_TEST = 1
    TEST_CLAUSE = TEST @Value(Continent) = North America
    TEST_MODE = TEST
    PASSED -> Tester_9
Note: larger 100000
Tester_9
    BOOL_OP = OR
    COMPOSITE_TEST = 1
    TEST_CLAUSE = TEST @Value(population) > 25000
    TEST_MODE = TEST
    PASSED -> CSV (writer JSON_7)
CSV (writer JSON_7)
    attributes: city string, city_ascii string, lat float, lng float, country string, iso2 string, iso3 string, admin_name string, capital string, population float, id int
